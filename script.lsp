(command "PLINE"
"5159.399,1115.2416"
"5259.399,1115.2416"
"5305.595,1145.2416"
"5335.595,1145.2416"
"5381.7909,1175.2416"
"5411.7909,1175.2416"
"5457.9869,1205.2416"
"5487.9869,1205.2416"
"5534.1828,1235.2416"
"5564.1828,1235.2416"
"5610.3787,1265.2416"
"5640.3787,1265.2416"
"5686.5747,1295.2416"
"5786.5747,1295.2416"
)
